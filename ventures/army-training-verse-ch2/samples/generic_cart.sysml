package Demo {
  part def GenericCart {
    attribute maxSpeed : Real = 3.0;
    attribute acceleration : Real = 0.8;
    attribute batteryWh : Real = 1200.0;
    attribute autonomous : Boolean = true;
  }
}
